(defun 	c:driver ( / )
	(drafting-settings)

)




; --- drafting-settings ---
; Notes:
; Arguments:
; None
; Alex Lundin 06-14-2017
(defun drafting-settings ( / )
  	(setvar "CMDECHO" 0)												;set CMDECHO to 0, supress commandline echo

	(setvar 'osmode 5)												;set osmode to 5
	;;;osmode integer is calculated from which osnaps you prefer
	;;;add the values for each item you would like
	;;;the result is the value of your osmode
	;;;options below"
	;;;0 NONe
	;;;1 ENDpoint
	;;;2 MIDpoint
	;;;4 CENter
	;;;8 NODe
	;;;16 QUAdrant
	;;;32 INTersection
	;;;64 INSertion
	;;;128 PERpendicular
	;;;256 TANgent
	;;;512 NEArest
	;;;1024 QUIck
	;;;2048 APParent Intersection
	;;;4096 EXTension
	;;;8192 PARallel

)

(vl-load-all "C:\\WS_Blocks\\Default\\LISP\\Lisp Functions\\OPENLOCATION.LSP")
(vl-load-all "C:\\WS_Blocks\\Default\\LISP\\Lisp Functions\\WattStopper.LSP")
(vl-load-all "C:\\WS_Blocks\\Default\\LISP\\Lisp Functions\\DLM Riser\\EBLOCK.LSP")
(vl-load-all "C:\\WS_Blocks\\Default\\LISP\\Lisp Functions\\DLM Riser\\EBLOCK2.LSP")
(vl-load-all "C:\\WS_Blocks\\Default\\LISP\\Lisp Functions\\DLM Riser\\EBLOCK3.LSP")
(vl-load-all "C:\\WS_Blocks\\Default\\LISP\\Lisp Functions\\DLM Riser\\EBLOCK4.LSP")
(vl-load-all "C:\\WS_Blocks\\Default\\LISP\\Lisp Functions\\DLM Riser\\GSR.lsp")
(vl-load-all "C:\\WS_Blocks\\Default\\LISP\\Lisp Functions\\DLM Riser\\GSR2.lsp")
(vl-load-all "C:\\WS_Blocks\\Default\\LISP\\Lisp Functions\\DLM Riser\\GSR3.LSP")
(vl-load-all "C:\\WS_Blocks\\Default\\LISP\\Lisp Functions\\DLM Riser\\GSR4.LSP")
(vl-load-all "C:\\WS_Blocks\\Default\\LISP\\Lisp Functions\\Drawing Utilities\\BackgroundColorToggle.lsp")
(vl-load-all "C:\\WS_Blocks\\Default\\LISP\\Lisp Functions\\Drawing Utilities\\CPSTYLE.LSP")
(vl-load-all "C:\\WS_Blocks\\Default\\LISP\\Lisp Functions\\Drawing Utilities\\CUSTOM-INSERT-SHORTCUTS.LSP")
(vl-load-all "C:\\WS_Blocks\\Default\\LISP\\Lisp Functions\\Drawing Utilities\\DXFCHECK.LSP")
(vl-load-all "C:\\WS_Blocks\\Default\\LISP\\Lisp Functions\\Drawing Utilities\\REPLACETEXTWITHBLOCK.lsp")
(vl-load-all "C:\\WS_Blocks\\Default\\LISP\\Lisp Functions\\Drawing Utilities\\WSHATCH.LSP")
(vl-load-all "C:\\WS_Blocks\\Default\\LISP\\Lisp Functions\\Drawing Utilities\\WSPAGESETUP.LSP")
(vl-load-all "C:\\WS_Blocks\\Default\\LISP\\Lisp Functions\\Drawing Utilities\\wsprint.lsp")
(vl-load-all "C:\\WS_Blocks\\Default\\LISP\\Lisp Functions\\Extractors\\WSQUOTETOOLBOM.lsp")
(vl-load-all "C:\\WS_Blocks\\Default\\LISP\\Lisp Functions\\File Reading\\read_excel_by_cell_range.LSP")
(vl-load-all "C:\\WS_Blocks\\Default\\LISP\\Lisp Functions\\Functions for Cable\\AUTOB.LSP")
(vl-load-all "C:\\WS_Blocks\\Default\\LISP\\Lisp Functions\\Functions for Cable\\AUTOV.LSP")
(vl-load-all "C:\\WS_Blocks\\Default\\LISP\\Lisp Functions\\Functions for Cable\\BRIDGES.LSP")
(vl-load-all "C:\\WS_Blocks\\Default\\LISP\\Lisp Functions\\Functions for Cable\\WSCABLE.LSP")
(vl-load-all "C:\\WS_Blocks\\Default\\LISP\\Lisp Functions\\Functions for Layout Blocks\\ATTFILTER.LSP")
(vl-load-all "C:\\WS_Blocks\\Default\\LISP\\Lisp Functions\\Functions for Layout Blocks\\GLOBALATTSYNC.LSP")
(vl-load-all "C:\\WS_Blocks\\Default\\LISP\\Lisp Functions\\Functions for Layout Blocks\\MASS-BLOCK-RENAME.LSP")
(vl-load-all "C:\\WS_Blocks\\Default\\LISP\\Lisp Functions\\Functions for Layout Blocks\\matchatts.LSP")
(vl-load-all "C:\\WS_Blocks\\Default\\LISP\\Lisp Functions\\Functions for Layout Blocks\\MIRRORALLBLOCKS.LSP")
(vl-load-all "C:\\WS_Blocks\\Default\\LISP\\Lisp Functions\\Functions for Layout Blocks\\NOID.LSP")
(vl-load-all "C:\\WS_Blocks\\Default\\LISP\\Lisp Functions\\Functions for Layout Blocks\\reset-block-attributes-to-default.LSP")
(vl-load-all "C:\\WS_Blocks\\Default\\LISP\\Lisp Functions\\Functions for Layout Blocks\\Test.LSP")
(vl-load-all "C:\\WS_Blocks\\Default\\LISP\\Lisp Functions\\Functions for Layout Blocks\\UPBS.LSP")
(vl-load-all "C:\\WS_Blocks\\Default\\LISP\\Lisp Functions\\Functions for Layout Blocks\\WSCPL.LSP")
(vl-load-all "C:\\WS_Blocks\\Default\\LISP\\Lisp Functions\\Functions for Layout Blocks\\WSCPRID.LSP")
(vl-load-all "C:\\WS_Blocks\\Default\\LISP\\Lisp Functions\\Functions for Layout Blocks\\WSFRONT.LSP")
(vl-load-all "C:\\WS_Blocks\\Default\\LISP\\Lisp Functions\\Functions for Layout Blocks\\WSHLT.LSP")
(vl-load-all "C:\\WS_Blocks\\Default\\LISP\\Lisp Functions\\Functions for Layout Blocks\\WSRID.LSP")
(vl-load-all "C:\\WS_Blocks\\Default\\LISP\\Lisp Functions\\Functions for Layout Blocks\\WSWP.LSP")
(vl-load-all "C:\\WS_Blocks\\Default\\LISP\\Lisp Functions\\Room Details\\EBLOCKRD.lsp")
(vl-load-all "C:\\WS_Blocks\\Default\\LISP\\Lisp Functions\\Room Details\\GRD.lsp")
(vl-load-all "C:\\WS_Blocks\\Default\\LISP\\Lisp Functions\\Room Details\\RDPOLYLINES.LSP")
(vl-load-all "C:\\WS_Blocks\\Default\\LISP\\Lisp Functions\\Room Details\\RDSETUP.LSP")
(vl-load-all "C:\\WS_Blocks\\Default\\LISP\\Lisp Functions\\Room Details\\RDVIEWPORTS.LSP")
(vl-load-all "C:\\WS_Blocks\\Default\\LISP\\Lisp Functions\\Run Time Updates\\RUNTIMEUPDATE.LSP")
(vl-load-all "C:\\WS_Blocks\\Default\\LISP\\Lisp Functions\\Script Creators\\PDFIMPORT.LSP")
(vl-load-all "C:\\WS_Blocks\\Default\\LISP\\Lisp Functions\\Script Creators\\RISERLAYOUT.lsp")
(vl-load-all "C:\\WS_Blocks\\Default\\LISP\\Lisp Functions\\Script Creators\\RISERLAYOUT2.LSP")
(vl-load-all "C:\\WS_Blocks\\Default\\LISP\\Lisp Functions\\Script Creators\\RISERLAYOUT3.LSP")
(vl-load-all "C:\\WS_Blocks\\Default\\LISP\\Lisp Functions\\Script Creators\\RISERLAYOUT4.LSP")
(vl-load-all "C:\\WS_Blocks\\Default\\LISP\\Lisp Functions\\Subfunction Library\\ACCESS-AND-MODIFY-BLOCK-TABLE.LSP")
(vl-load-all "C:\\WS_Blocks\\Default\\LISP\\Lisp Functions\\Subfunction Library\\CUSTOM-ENTMOD.LSP")
(vl-load-all "C:\\WS_Blocks\\Default\\LISP\\Lisp Functions\\Subfunction Library\\DEFAULT-ERROR-HANDLER.LSP")
(vl-load-all "C:\\WS_Blocks\\Default\\LISP\\Lisp Functions\\Subfunction Library\\ENTITY-TO-BLOCK-TRUENAME.LSP")
(vl-load-all "C:\\WS_Blocks\\Default\\LISP\\Lisp Functions\\Subfunction Library\\GET-BLOCK-ATTRIBUTE-TAGS-AND-VALUES-LIST.lsp")
(vl-load-all "C:\\WS_Blocks\\Default\\LISP\\Lisp Functions\\Subfunction Library\\GET-STANDARD-AUTOCAD-APPLICATION-OBJECTS.LSP")
(vl-load-all "C:\\WS_Blocks\\Default\\LISP\\Lisp Functions\\Subfunction Library\\RELEASE-OBJECTS.LSP")
(vl-load-all "C:\\WS_Blocks\\Default\\LISP\\Lisp Functions\\Subfunction Library\\ROOMID-STRING-FORMATER.LSP")
(vl-load-all "C:\\WS_Blocks\\Default\\LISP\\Lisp Functions\\Subfunction Library\\SELECT-ENTIRE-LAYER.LSP")
(vl-load-all "C:\\WS_Blocks\\Default\\LISP\\Lisp Functions\\Subfunction Library\\SELECTION-WITH-TRUENAME-FILTER.lsp")
(vl-load-all "C:\\WS_Blocks\\Default\\LISP\\Lisp Functions\\Subfunction Wrappers\\TEST.LSP")
(vl-load-all "C:\\WS_Blocks\\Default\\LISP\\Lisp Functions\\Subfunction Wrappers\\WRAPPER-CUSTOM-ENTMOD-1.LSP")
(vl-load-all "C:\\WS_Blocks\\Default\\LISP\\Lisp Functions\\Subfunction Wrappers\\WRAPPER-CUSTOM-ENTMOD-2.LSP")
(vl-load-all "C:\\WS_Blocks\\Default\\LISP\\Lisp Functions\\Subfunction Wrappers\\WRAPPER-ROOMID-FORMAT-1.LSP")
(vl-load-all "C:\\WS_Blocks\\Default\\LISP\\Lisp Functions\\Subfunction Wrappers\\WRAPPER-ROOMID-FORMAT-2.LSP")
(vl-load-all "C:\\WS_Blocks\\Default\\LISP\\Lisp Functions\\Subfunction Wrappers\\WRAPPER-ROOMID-FORMAT-3.LSP")
(vl-load-all "C:\\WS_Blocks\\Default\\LISP\\Lisp Functions\\Templates\\new Function Template.LSP")
(vl-load-all "C:\\WS_Blocks\\Default\\LISP\\Lisp Functions\\Templates\\new Sub-Function Template.LSP")
(vl-load-all "C:\\WS_Blocks\\Default\\LISP\\Lisp Functions\\Titleblocks\\MTB.LSP")
(vl-load-all "C:\\WS_Blocks\\Default\\LISP\\Lisp Functions\\Titleblocks\\WSMTB.LSP")
(vl-load-all "C:\\WS_Blocks\\Default\\LISP\\Lisp Functions\\Titleblocks\\WSNEW.LSP")
(vl-load-all "C:\\WS_Blocks\\Default\\LISP\\Lisp Functions\\Titleblocks\\WSTB-functions.LSP")
(vl-load-all "C:\\WS_Blocks\\Default\\LISP\\Lisp Functions\\Vantage Riser\\EBLOCKVANTAGE.lsp")
(vl-load-all "C:\\WS_Blocks\\Default\\LISP\\Lisp Functions\\Vantage Riser\\GSRVANTAGE.LSP")
(vl-load-all "C:\\WS_Blocks\\Default\\LISP\\Lisp Functions\\Vantage Riser\\VMAIN.LSP")
(load "acadoptions.lsp")
(c:acadoptions)
(vl-load-all "WriteAllLISPToACAD.lsp")
(load "RUNTIMEUPDATE.LSP")
(c:runtimeupdate)
